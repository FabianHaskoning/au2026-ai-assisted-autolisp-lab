;;; ---------------------------------------------------------------------
;;; prefix-util.lsp
;;;
;;; Reusable helper functions for the "prefix" routine: calculations,
;;; small building blocks used by prefix-core.lsp and prefix-command.lsp.
;;; No (defun c:...) commands belong in this file - only internal
;;; helpers.
;;; ---------------------------------------------------------------------

(defun prefix-example (/ )
  ;; TODO: replace with a real helper, e.g. a distance or midpoint
  ;; calculation used by the rest of this routine.
  nil
)
