;;; ============================================================================
;;;  rdb-dialog.lsp  -  DCL dialog (embedded, written to a temp file)
;;; ============================================================================

;; Write the embedded DCL to a temp file; return its path.
(defun rdb-write-dcl ( / f path)
  (setq path (vl-filename-mktemp "roundabout.dcl"))
  (setq f (open path "w"))
  (write-line "roundabout : dialog {"                                                          f)
  (write-line "  label = \"Roundabout\";"                                                      f)
  (write-line "  : row {"                                                                      f)
  (write-line "    : boxed_radio_column { label = \"Type\"; key = \"type_grp\";"               f)
  (write-line "        : radio_button { key = \"rb_urban\"; label = \"urban (16.00/10.50)\"; }" f)
  (write-line "        : radio_button { key = \"rb_rural\"; label = \"rural (18.00/12.75)\"; } }" f)
  (write-line "    : boxed_column { label = \"Core [m]\";"                                     f)
  (write-line "        : edit_box { key = \"eb_rb\"; label = \"Outer radius Rb:\"; edit_width = 7; }" f)
  (write-line "        : edit_box { key = \"eb_ri\"; label = \"Inner radius Ri:\"; edit_width = 7; }" f)
  (write-line "        : edit_box { key = \"eb_ro\"; label = \"Central island Ro:\"; edit_width = 7; }" f)
  (write-line "        : text { key = \"tx_carr\"; label = \"Carriageway width: 0.00 m\"; width = 26; }" f)
  (write-line "        : text { key = \"tx_mount\"; label = \"Mountable apron: 0.00 m\"; width = 26; } }" f)
  (write-line "  }"                                                                            f)
  (write-line "  : row {"                                                                      f)
  (write-line "    : boxed_column { label = \"Arm [m]\";"                                      f)
  (write-line "        : edit_box { key = \"eb_we\";   label = \"Entry width we:\";     edit_width = 7; }" f)
  (write-line "        : edit_box { key = \"eb_wx\";   label = \"Exit width wx:\";      edit_width = 7; }" f)
  (write-line "        : edit_box { key = \"eb_wm\";   label = \"Splitter width wm:\";  edit_width = 7; }" f)
  (write-line "        : edit_box { key = \"eb_ls\";   label = \"Splitter length Ls:\"; edit_width = 7; }" f)
  (write-line "        : edit_box { key = \"eb_re\";   label = \"Entry radius Re:\";    edit_width = 7; }" f)
  (write-line "        : edit_box { key = \"eb_rx\";   label = \"Exit radius Rx:\";     edit_width = 7; }" f)
  (write-line "        : edit_box { key = \"eb_larm\"; label = \"Arm length Larm:\";    edit_width = 7; } }" f)
  (write-line "    : boxed_column { label = \"Cycle path [m]\";"                               f)
  (write-line "        : toggle   { key = \"cb_cycle\"; label = \"Draw cycle ring\"; }"        f)
  (write-line "        : edit_box { key = \"eb_verge\"; label = \"Verge:\";       edit_width = 7; }" f)
  (write-line "        : edit_box { key = \"eb_wbike\"; label = \"Cycle width:\"; edit_width = 7; }" f)
  (write-line "        : toggle   { key = \"cb_mark\";  label = \"Crossing marking\"; }"       f)
  (write-line "        : toggle   { key = \"cb_drop\";  label = \"Teardrop splitter\"; } }"    f)
  (write-line "  }"                                                                            f)
  (write-line "  spacer;"                                                                      f)
  (write-line "  ok_cancel ;"                                                                  f)
  (write-line "}"                                                                              f)
  (close f)
  path)

;; Recompute the read-only text tiles.
(defun rdb-refresh-readonly ( / rb ri ro)
  (setq rb (rdb-atof (get_tile "eb_rb"))
        ri (rdb-atof (get_tile "eb_ri"))
        ro (rdb-atof (get_tile "eb_ro")))
  (set_tile "tx_carr" (strcat "Carriageway width: " (rtos (- rb ri) 2 2) " m"))
  (set_tile "tx_mount" (strcat "Mountable apron: " (rtos (- ri ro) 2 2) " m")))

;; Read all tiles into the command-scope variables (dynamic binding).
(defun rdb-read-values ()
  (setq Rb     (rdb-atof (get_tile "eb_rb"))
        Ri     (rdb-atof (get_tile "eb_ri"))
        Ro     (rdb-atof (get_tile "eb_ro"))
        we     (rdb-atof (get_tile "eb_we"))
        wx     (rdb-atof (get_tile "eb_wx"))
        wm     (rdb-atof (get_tile "eb_wm"))
        Ls     (rdb-atof (get_tile "eb_ls"))
        Re     (rdb-atof (get_tile "eb_re"))
        Rx     (rdb-atof (get_tile "eb_rx"))
        lArm   (rdb-atof (get_tile "eb_larm"))
        verge  (rdb-atof (get_tile "eb_verge"))
        wbike  (rdb-atof (get_tile "eb_wbike"))
        doCycle (= "1" (get_tile "cb_cycle"))
        doMark  (= "1" (get_tile "cb_mark"))
        doDrop  (= "1" (get_tile "cb_drop"))))

(princ)
